#usage "<b>TM245P pick and place file generator</b>\n"
"<p>Generates control files for the TM245P pick and place machine.</p>"
"<author>Authored by Jamie Laing (jlaing@ChicagoRobotics.net), based on work done by Patrick Van Oosterwijck (patrick@silicognition.com),"
"adapted from code found on DangerousPrototypes.com</author>"

// Provided as is, without warranty.  Use at your own risk.

void saveLayer(string strTargetLayer) {
	int intTargetLayer = 1;
	if (strTargetLayer == "Bottom") {
		intTargetLayer = 16;
	}

	board(B) {
		string strFilePath = filedir(B.name);
		string strFileName = strFilePath + "Neoden4-" + strTargetLayer + "-Layer " + filename(B.name);
		string fileSave = filesetext(strFileName, ".csv");

		string strSaveName = dlgFileSave(strTargetLayer + " - Save File", fileSave, "*.csv");

		if (fileSave == "") {
			exit(0);
		}

		real mx = -1.0;
		real my = -1.0;
		real cx = 0.0;
		real cy = 0.0;

		int Result = dlgDialog("Machine parameters") {
			dlgGridLayout{
				dlgCell(0,0) dlgLabel("Machine xy of the first component:");
				dlgCell(0,1) dlgRealEdit(mx, -1.0, 1000.0);
				dlgCell(0,2) dlgRealEdit(my, -1.0, 1000.0)
			}
			dlgSpacing(10);
			dlgHBoxLayout {
				dlgPushButton("+Generate Top") {
					dlgAccept();
					output(strSaveName) {
						printf("Designator,Footprint,Mid X,Mid Y,Layer,Rotation,Comment\n");
						int first = 0;
						B.elements(E) {
							int wasSmd = 0;
							real angle = 0;

							E.package.contacts(C) {
								if (C.smd && C.smd.layer == 1) {
									wasSmd = 1;
								}
							}

							if (wasSmd) {
								string strMPN = "";
								E.attributes(A) {
									if (A.name == "MPN") {
										strMPN = A.value;
									}
								}

								string strFootprint = "";

								if (E.angle <= 180)
									angle = E.angle;
								else
									angle = E.angle - 360;
								if (first == 0) {
									mx = mx - u2mm(E.x);
									my = my - u2mm(E.y);
									cx = u2mm(E.x) + mx;
									cy = u2mm(E.y) + my;
									first = 1;
								}
								else {
									cx = u2mm(E.x) + mx;
									cy = u2mm(E.y) + my;
								}
								printf("%s,%s,%.2fmm,%.2fmm,T,%.0f,%s\n", E.name, E.package.name, cx, cy, angle, strMPN);
							}
						}
					}
				}
				dlgPushButton("+Generate Bottom") {
					dlgAccept();
				}
				dlgPushButton("-Cancel") {
					dlgReject();
				}
			}
		};
	}
}

if (board) board(B) {
	//saveLayer("Top");
	//saveLayer("Bottom");
}
else {
	dlgMessageBox("\n    Start this ULP in a Board    \n");
	exit(0);
}
