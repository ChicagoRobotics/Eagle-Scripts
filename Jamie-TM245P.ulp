#usage "<b>TM245P pick and place file generator</b>\n"
       "<p>"
       "Generates control files for the TM245P pick and place machine."
       "</p>"
       "<author>Modified by Jamie Laing, Authored by Patrick Van Oosterwijck (patrick@silicognition.com),"
       "adapted from code found on DangerousPrototypes.com</author>"

// THIS PROGRAM IS PROVIDED AS IS AND WITHOUT WARRANTY OF ANY KIND, EXPRESSED OR IMPLIED


if (board) board(B) {

  // Get filename
  string fileName = dlgFileSave("Top - Save File", filesetext(B.name, "-top.csv"), "*.csv");
  if (fileName == "") exit(0);

  output(fileName) {
    int line = 1;

	  printf("#%s TOP\n#Stack,X1,Y1,X2,Y2,Pick Depth,Place Depth,Pick Delay,Place Delay,SizeX,"
	      "SizeY,Rate,Speed,Torque,Vacuum 1,Vacuum 2,Vacuum Off,Calibration,Skip,,,,\n"
	      "#Stack_S,X1,Y1,X2,Y2,Pick Depth,Place Depth,Pick Delay,Place Delay,SizeX,SizeY,"
	      "Rate,Speed,Torque,Vacuum 1,Vacuum 2,Vacuum Off,Calibration,Skip,Chip X,Chip Y,"
	      "Loop X,Loop Y\n#Board,OffsetX,OffsetY,Skip\n"
	      "10201,0,0,0,,\n#Component,Nozzle,Stack,X,Y,Angle,Skip,Name,Value\n", B.name);

    B.elements(E) {
      int wasSmd = 0,
          xmax =-2147483648,
          xmin = 2147483647,
          ymax = xmax,
          ymin = xmin;
      real angle = 0;

      E.package.contacts(C) {
        if (C.smd && C.smd.layer == 1) {
          wasSmd = 1;

          if (C.x > xmax) xmax = C.x;
          if (C.y > ymax) ymax = C.y;
          if (C.x < xmin) xmin = C.x;
          if (C.y < ymin) ymin = C.y;
        }
      }
      
      if (wasSmd) {

			string strMPN = "";
			E.attributes(A){
				if(A.name == "MPN"){
					strMPN = A.value;
				}
			}

		    if(E.angle <= 180)
		      angle = E.angle;
		    else
		      angle = E.angle - 360;

	      printf("%d,1,,%.0f,%.0f,%.0f,0,%s,%s\n",
            line++, u2mic((xmin + xmax)/2), u2mic((ymin + ymax)/2),
            angle, E.name, strMPN);
	    }
    }
  }

  // Get filename
  fileName = dlgFileSave("Bottom - Save File", filesetext(B.name, "-bot.csv"), "*.csv");
  if (fileName == "") exit(0);

  output(fileName) {
    int line = 1;

	  printf("#%s BOTTOM\n#Stack,X1,Y1,X2,Y2,Pick Depth,Place Depth,Pick Delay,Place Delay,SizeX,"
	      "SizeY,Rate,Speed,Torque,Vacuum 1,Vacuum 2,Vacuum Off,Calibration,Skip,,,,\n"
	      "#Stack_S,X1,Y1,X2,Y2,Pick Depth,Place Depth,Pick Delay,Place Delay,SizeX,SizeY,"
	      "Rate,Speed,Torque,Vacuum 1,Vacuum 2,Vacuum Off,Calibration,Skip,Chip X,Chip Y,"
	      "Loop X,Loop Y\n#Board,OffsetX,OffsetY,Skip\n"
	      "10201,0,0,0,,\n#Part,Nozzle,Stack,X,Y,Angle,Skip,Name,Value\n", B.name);

    B.elements(E) {
      int wasSmd = 0,
          xmax =-2147483648,
          xmin = 2147483647,
          ymax = xmax,
          ymin = xmin;
      real angle = 0;

      E.package.contacts(C) {
        if (C.smd && C.smd.layer == 16) {
          wasSmd = 1;

          if (C.x > xmax) xmax = C.x;
          if (C.y > ymax) ymax = C.y;
          if (C.x < xmin) xmin = C.x;
          if (C.y < ymin) ymin = C.y;
        }
      }

	  string strMPN = "";
	  E.attributes(A) {
		  if (A.name == "MPN") {
			  strMPN = A.value;
		  }
	  }

      if (wasSmd) {
		    if(E.angle <= 180)
		      angle = E.angle;
		    else
		      angle = E.angle - 360;

			printf("%d,1,,%.0f,%.0f,%.0f,0,%s,%s\n",
				line++, u2mic((xmin + xmax) / 2), u2mic((ymin + ymax) / 2),
				angle, E.name, strMPN);
	    }
    }
  }
} else {
  dlgMessageBox("\n    Start this ULP in a Board    \n");
  exit(0);
}
